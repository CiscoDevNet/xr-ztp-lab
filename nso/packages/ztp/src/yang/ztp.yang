module ztp {

  namespace "http://example.com/ztp";
  prefix ztp;

  import ietf-inet-types {
    prefix inet;
  }
  import tailf-common {
    prefix tailf;
  }
  import tailf-ncs {
    prefix ncs;
  }

  description
    "ZTP service for device day0 configuration and onboarding";

  revision 2016-01-01 {
    description
      "Initial revision.";
  }

  list ztp {

    key serial;
    leaf serial {
        tailf:cli-allow-range;
        type string;
    }

    leaf hostname {
        type string;
    }

    leaf day0{
        type string;
        mandatory true;
    }

    leaf ip{
        type inet:ipv4-address;
        mandatory true;
    }

    description "ZTP NSO service";

      tailf:action get_day0 {
        tailf:actionpoint get_day0-actionpoint;
        input {
        }
        output {
          leaf message {
            type string;
          }
        }
      }


       tailf:action onboard {
        tailf:actionpoint onboard-actionpoint;
        input {
        }
        output {
          leaf message {
            type string;
          }
        }
      }
  }
  
  notification ztp-status {
      leaf state {
	type string;
        mandatory true;
      }
      leaf device {
	type string;
        mandatory true;
      }
  }
  
}
